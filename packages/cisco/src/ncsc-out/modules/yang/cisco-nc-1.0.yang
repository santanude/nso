module cisco-nc-1.0 {
  yang-version 1.1;
  namespace "http://tail-f.com/ns/ned-id/cisco-nc-1.0";
  prefix cisco-nc-1.0;

  import cisco-nc {
    prefix family;
  }

  identity cisco-nc-1.0 {
    base family:cisco-nc;
  }
}
