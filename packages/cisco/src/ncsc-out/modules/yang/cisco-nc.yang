module cisco-nc {
  yang-version 1.1;
  namespace "http://tail-f.com/ns/ned-id/cisco-nc";
  prefix cisco-nc;

  import tailf-common {
    prefix tailf;
  }

  import tailf-ncs-ned {
    prefix ned;
  }

  identity cisco-nc {
    tailf:abstract;
    base ned:netconf-ned-id;
  }
}
